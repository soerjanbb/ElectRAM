# Electram Requirements

## Part 23 Requirements (Functional)

### Climb Gradients (Functional)

#### OEI Climb Gradient: > 2% (Functional)

#### 23.2120: AEO Climb Gradient: > 4% (Functional)
2 percent climb gradient at 400 feet (122 meters) above the takeoff surface with the landing gear retracted and flaps in the approach configuration(s).

### Weight: MTOW < 19,000 lbs (Functional)

## Performance Requirements: Measure of Merit Requirements (Functional)

### Passenger Count: 19 Passengers (Functional)
Aircraft shall have 19 passengers.

### Range: Range > 300 nm (Functional)

### Takeoff: Takeoff Distance < 2600 ft (Functional)

### Landing: Landing Distance < 2600 ft (Functional)

### Endurance: 45 min fuel reserves (Functional)

### Air Stair: Door Stair (Functional)

## RFP: RFP Requirements (Functional)

### TO/LD Distance: Less than 4000 ft (Functional)

### EIS: 2035 (Systems certifiable by 2034) (Functional)

### Passenger Capacity: Greater than 9 (Functional)
Passenger count shall be greater than 9

### Wingspan Limit: < 36 m (Functional)

### Range: Range > 300 nm (Functional)

### Propulsion: Multi-engine Configuration (Functional)

### Reliability: ≥ current equivalent aircraft (Functional)
Multiengine configuration (tip and BLI)

### Noise: FAR Part 36 §36.301(c) compliant (Functional)
Max propeller tip speed is less than 0.9 Mach

### Maintenance Cost: Lower than current equivalents (Functional)
Annual cost is less than $4.4 million
